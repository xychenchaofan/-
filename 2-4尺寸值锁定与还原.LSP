;;;-----------------------------------------------------------------------------------;;
;;;名称:  尺寸锁定  命令:dsd                                                          ;;
;;;说明:  锁定dimlock或还原dimunlock标注尺寸的值                                             ;;
;;;       默认选项是锁定，注意解锁的同时，尺寸值会还原成测量值
(defun c:dsd (/ ss ss_lst flag)
  (setq ss (ssget (list '(0 . "DIMENSION,ARC_DIMENSION"))))
  (setq ss_lst (ss->lst ss))
  (initget "s a")
  (setq flag (getkword "\n[锁定标注尺寸值(s)/还原尺寸值(a)]"))
  (if (or (= flag nil) (= flag "s"))
	(foreach x ss_lst (dimlock x))
	(foreach x ss_lst (dimunlock x))
  )
  (princ)
)
(defun dimlock (diment /)
  (setq dxf (entget diment)
	content (cdr (assoc 1 dxf))
	txt (rtos (cdr (assoc 42 dxf)) 2 0)
	)
  (cond ( (eq content "")
         (setq dxf (subst (cons 1 txt) (assoc 1 dxf) dxf))
	 )
        ( (wcmatch content "*=*")
         (setq position (vl-string-position (ascii"=") content)
	    len (strlen content)
	    )
         (setq tidai (substr content (+ position 2) (- len position))
	    txt (vl-string-subst txt tidai content)
	    )
        (setq dxf (subst (cons 1 txt) (assoc 1 dxf) dxf))
	)
  )
  (entmod dxf)
)
(defun dimunlock (diment / )
  (setq dxf (entget diment))
  (setq dxf (subst (cons 1 "") (assoc 1 dxf) dxf))
  (entmod dxf)
)
;;;-----------------------------------------------------------------------------------;;
