;;;=====================================================================================;;
;;;名称:  关闭某层  命令:cgb                                                         <4>;;
;;;功能： 将选定图元所在的图层列表中的图层都关闭（不显示）                              ;;
(defun c:cgb ()
  (princ "\n请选择需要关闭的图层上的图元")
  (setq ss (ssget))
  (setq entlst (ss->lst ss))
  (setq Laylist
    (delsame (mapcar '(lambda(x) (cdr (assoc 8 (entget x))) ) entlst));返回entlst中的图元所在的图层列表
  )
  (layer?open nil Laylist)
)
;;;                                   End of File                                    <4>;;
;;;-------------------------------------------------------------------------------------;;
