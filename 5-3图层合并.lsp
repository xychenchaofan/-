;;;=====================================================================================;;
;;;名称:  图层合并  命令:chb                                                         <1>;;
;;;说明： 可以实现多个图层合并、删除、提取等操作，对话框模式，无按钮快捷键启动          ;;
;;;引用： 图层管理sstc.VLX (外部引用)                                                   ;;
(defun c:chb ()
  (if (not (member '"C:SSTC" (vl-list-exported-functions)))
    (progn
      (setq fn (getfiled "打开文件SSTC.VLX" "" "vlx" 4))
      (if fn (load fn ) (princ "\n未找到文件"))
    )
  )
  (c:sstc)
)

(defun c:ch()
  (vl-cmdf "laymrg" "n" "")
)
;;;                                   End of File                                    <1>;;
;;;-------------------------------------------------------------------------------------;;
