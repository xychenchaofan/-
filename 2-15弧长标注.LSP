;;;-----------------------------------------------------------------------------------;;
;;;名称:  弧长标注                                                                    ;;
;;;命令:  hc                                                                          ;;
;;;说明:  连续标注弧长,esc及右键退出，仅支持圆弧                                      ;;
;;;引用:  chc                                                                         ;;
;;;-----------------------------------------------------------------------------------;;
(defun c:hc(/ ent)
  (setq ent (centsel "\n选择一条圆弧线" "ARC"))
  (if ent
    (chc ent)
    )
  (princ)
)
