;;;----------------------------------------------------;
;;;功能: 点到直线的垂足                                ;
;;;输入: 要求的点Pt，和直线的两个端点P1,P2             ;
;;;输出: 所求的垂足                                    ;
;;;----------------------------------------------------;
(defun LINE:Perpendicular_Foot_1 (pt p1 p2)
  (inters pt (mapcar '+ pt (MAT:Rot90 (mapcar '- p1 p2))) p1 p2 nil)
)
;修剪标注的尺寸线
(defun c:trd()
  (setq pt1 (getpoint "指定切线上一点")
	pt2 (getpoint pt1 "指定切线上另一点")
	)
  (if (not (and pt1 pt2)) (exit))
  (setq ss (ssget "f" (list pt1 pt2) '((0 . "DIMENSION"))))
  (if (equal ss nil) (setq ss (ssget '((0 . "DIMENSION")))))
  (if ss (setq ss_lst (ss->lst ss)) (exit))
  (foreach x ss_lst
    (setq dxf (entget x)
	  pt10 (cdr (assoc 10 dxf))
	  pt13 (cdr (assoc 13 dxf))
	  pt14 (cdr (assoc 14 dxf))
	  )
    (setq ptx (LINE:Perpendicular_Foot_1 pt13 pt14 pt10)
	  vector1 (mapcar '- pt13 ptx)
	  pt9 (mapcar '+ vector1 pt10)
	  )
    (setq new_pt13 (inters pt13 pt9 pt1 pt2 nil)
	  new_pt14 (inters pt14 pt10 pt1 pt2 nil)
	  )
    (setq dxf (subst (cons 13 new_pt13) (assoc 13 dxf) dxf)
	  dxf (subst (cons 14 new_pt14) (assoc 14 dxf) dxf)
	  )
    (entmod dxf)
  )
)
(defun c:dtr()
  (prompt "选择需要修剪尺寸线的标注")
  (setq ss (ssget '((0 . "DIMENSION"))))
  (if ss (setq ss_lst (ss->lst ss)) (exit))
  (setq pt1 (getpoint "指定切线上一点")
	pt2 (getpoint pt1 "指定切线上另一点")
	)
  (if (not (and pt1 pt2)) (exit))
  (foreach x ss_lst
    (setq dxf (entget x)
	  pt10 (cdr (assoc 10 dxf))
	  pt13 (cdr (assoc 13 dxf))
	  pt14 (cdr (assoc 14 dxf))
	  )
    (setq ptx (LINE:Perpendicular_Foot_1 pt13 pt14 pt10)
	  vector1 (mapcar '- pt13 ptx)
	  pt9 (mapcar '+ vector1 pt10)
	  )
    (setq new_pt13 (inters pt13 pt9 pt1 pt2 nil)
	  new_pt14 (inters pt14 pt10 pt1 pt2 nil)
	  )
    (setq dxf (subst (cons 13 new_pt13) (assoc 13 dxf) dxf)
	  dxf (subst (cons 14 new_pt14) (assoc 14 dxf) dxf)
	  )
    (entmod dxf)
  )
)
